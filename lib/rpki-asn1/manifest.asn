-- Declaration for c->asn compatibility
--
--

DEFINITIONS IMPLICIT TAGS ::=
-- imports
IMPORTS AlgorithmIdentifier FROM Algorithms IN Algorithms.asn,
        Extensions IPAddressOrRangeA Attribute FROM extensions IN extensions.asn,
        Certificate Version FROM certificate IN certificate.asn,
        Name FROM name IN name.asn;

-- Manifest Specification

   Manifest ::= SEQUENCE
    {
    version         [0] Manifestversion DEFAULT v1,
    manifestNumber  INTEGER,
    thisUpdate      GeneralizedTime,
    nextUpdate      GeneralizedTime,
    fileHashAlg     OBJECT IDENTIFIER,
    fileList        SEQUENCE SIZE (0..MAX) OF FileAndHash
    }

    Manifestversion ::= INTEGER { v1(0) } (v1)

FileAndHash ::= SEQUENCE
    {
    file        IA5String,
    hash        BIT STRING
    }

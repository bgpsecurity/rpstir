-- File:     blob.asn
-- Contents: ASN.1 specification for a signed blob
-- System:   PKIM development.
-- Created:  April 12, 2011
-- Author:   Charlie Gardiner
--


DEFINITIONS ::= -- explicitly encoded !

IMPORTS AlgorithmIdentifier FROM Algorithms IN Algorithms.asn;

Blob ::= SIGNED  ANY

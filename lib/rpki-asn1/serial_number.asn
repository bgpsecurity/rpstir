-- File:     serial_number.asn
-- Contents: ASN.1 specification for serial number
-- System:   PKIM development.
-- Created:  4-Nov-1996
-- Author:   charlie/jduffy
--
-- Remarks: Workaround for recursive include compiler problem
--          serial number needed by extensions.h and certificates.h
--


DEFINITIONS ::= -- explicitly encoded !

EXPORTS
      SerialNumber;

SerialNumber ::= INTEGER

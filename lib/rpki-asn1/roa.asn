DEFINITIONS IMPLICIT TAGS ::=

RouteOriginAttestation ::= SEQUENCE {
    version [0] ROAversion DEFAULT v1,
    asID ASID,
    ipAddrBlocks ROAIPAddrBlocks
}

ROAversion ::= INTEGER { v1(0) } (v1)

ASID ::= INTEGER

ROAIPAddrBlocks ::= SEQUENCE (SIZE (1..MAX)) OF ROAIPAddressFamily

ROAIPAddressFamily ::= SEQUENCE {
    addressFamily OCTET STRING (SIZE (2..3)),
    addresses SEQUENCE (SIZE (1..MAX)) OF ROAIPAddress
}

ROAIPAddress ::= SEQUENCE {
    address IPAddress,
    maxLength INTEGER OPTIONAL
}

IPAddress ::= BIT STRING

-- $Id$
-- Dec 20 2000 511E  */
-- Dec 20 2000 PFOLEY added domain name form
-- Nov 13 2000 466E  */
-- Nov 13 2000 GARDINER started
-- sfcsid = "@(#)name.asn 511E"
-- File:     name.asn
-- Contents: ASN.1 specification for X.509 Name
-- System:   PKIM development.
-- Created:  13-Feb-1996
-- Author:   nyang
--
-- Remarks:
--
-- $Header: /u4/PKI/cms3_3/Libraries/Dev/rcs/lib/asndefs/name.asn,v 1.3 1997/11/05 20:51:07 mcasagni Exp $ 
--


DEFINITIONS ::= -- explicitly encoded !
BEGIN

EXPORTS Name, RDNSequence, DistinguishedName, RelativeDistinguishedName,
AttributeValueAssertion, ub-name, DirectoryString;

Name ::= CHOICE {
    RDNSequence}

RDNSequence ::= SEQUENCE OF RelativeDistinguishedName

DistinguishedName ::= RDNSequence

RelativeDistinguishedName ::= SET OF AttributeValueAssertion

AttributeValueAssertion ::= SEQUENCE {
	objid               OBJECT IDENTIFIER TABLE SelectedAttributeTypes,
	value               ANY DEFINED BY objid }


-- Temporary structure to store specific attribute value for use by
-- ufn_to_obj

AttributeValueChoice ::= SEQUENCE {
	objid		OBJECT IDENTIFIER,
	value		DirectoryString }

-- This section is a partial list of SelectedAttributeTypes.
-- Many will be left out or commented out in order to save
-- space and reduce complexity.  Note the the set of allowable
-- attributes is constrained anyway.
--
-- NOTE: This table makes use of the "catch-all" ability introduced in asn_gen v1.4.
-- This allows for correct decoding (and re-encoding) of any valid
-- ASN.1 syntax without requiring the application to understand the semantics.  
-- This means: Your application won't core-dump
-- when you are presented with a Certificate containing attributes
-- that you don't know how process.

SelectedAttributeTypes ::= TABLE {
--    objectClass           id-objectClass            ObjectClass,
--    aliasedObjectName     id-aliasedObjectName      AliasedObjectName,
--    knowledgeInformation  id-knowledgeInformation   DirectoryString,
    commonName              id-commonName             DirectoryString (SIZE (1..ub-common-name)),
    surname                 id-surname                DirectoryString (SIZE (1..ub-surname)),
    serialNumber            id-serialNumber           PrintableString (SIZE (1..ub-serial-number)),
    countryName             id-countryName            PrintableString (SIZE (2)),
    localityName            id-localityName           DirectoryString (SIZE (1..ub-locality-name)),
    stateOrProvinceName     id-stateOrProvinceName    DirectoryString (SIZE (1..ub-state-name)),
    streetAddress           id-streetAddress          DirectoryString (SIZE (1..ub-street-address)),
    organizationName        id-organizationName       DirectoryString (SIZE (1..ub-organization-name)),
    organizationalUnitName  id-organizationalUnitName DirectoryString (SIZE (1..ub-organizational-unit-name)),
    title                   id-title                  DirectoryString (SIZE (1..ub-title)),
    description             id-description            DirectoryString (SIZE (1..ub-description)),
--    searchGuide           id-searchGuide            Criteria,
    businessCategory        id-businessCategory       DirectoryString (SIZE (1..ub-business-category)),
--    postalAddress         id-postalAddress          PostalAddress,
    postalCode              id-postalCode             DirectoryString (SIZE (1..ub-postal-code)),
    postOfficeBox           id-postOfficeBox          DirectoryString (SIZE (1..ub-post-office-box)),
    physicalDeliveryOfficeName id-physicalDeliveryOfficeName DirectoryString (SIZE (1..ub-physical-office-name)),
    telephoneNumber         id-telephoneNumber        PrintableString (SIZE (1..ub-telephone-number)),
--    telexNumber           id-telexNumber            TelexNumber,
--    teletexTerminalIdentifier id-teletexTerminalIdentifier TeletexTerminalIdentifier,
--    facsimileTelephoneNumber id-facsimileTelephoneNumber FacsimileTelephoneNumber,
    x121Address             id-x121Address            NumericString (SIZE (1..ub-x121-address)),
    internationalISDNNumber id-internationalISDNNumber NumericString (SIZE (1..ub-isdn-address)),
--    registeredAddress     id-registeredAddress      PostalAddress,
    destinationIndicator    id-destinationIndicator   PrintableString (SIZE (1..ub-destination-indicator)),
--    preferredDeliveryMethod id-preferredDeliveryMethod PreferredDeliveryMethod,
--    presentationAddress   id-presentationAddress    PresentationAddress,
--    supportedApplicationContext id-supportedApplicationContext ObjectIdentifier,
--    member                id-member                 DistinguishedName,
--    owner                 id-owner                  DistinguishedName,
--    roleOccupant          id-roleOccupant           DistinguishedName,
--    seeAlso               id-seeAlso                DistinguishedName,
    userPassword            id-userPassword           OCTET STRING (SIZE (1..ub-user-password)),
--    userCertificate       id-userCertificate        UserCertificate,
--    cACertificate         id-cACertificate          cACertificate,
--    authorityRevocationList id-authorityRevocationList AuthorityRevocationList,
--    certificateRevocationList id-certificateRevocationList CertificateRevocationList,
--    crossCertificatePair id-crossCertificatePair    CrossCertificatePair,
--    etc.
    name                    id-name                   DirectoryString(SIZE (1..ub-name)),
    ipAddress               id-ipAddress              PrintableString(SIZE (1..ub-ipAddress)),
    uniqueIdentifier        id-at-uniqueIdentifier    BIT STRING,
    emailAddress            id-emailAddress           IA5String,
    domainNameForm          id-at-dc                  IA5String,
    unknown                 0xFFFF      ANY     -- has to be last item in table
}

ub-common-name              INTEGER ::= 64
ub-surname                  INTEGER ::= 64
ub-serial-number            INTEGER ::= 64
ub-locality-name            INTEGER ::= 128
ub-state-name               INTEGER ::= 128
ub-street-address           INTEGER ::= 128
ub-organization-name        INTEGER ::= 64
ub-organizational-unit-name INTEGER ::= 64
ub-title                    INTEGER ::= 64
ub-description              INTEGER ::= 1024
ub-business-category        INTEGER ::= 128
ub-postal-code              INTEGER ::= 40
ub-post-office-box          INTEGER ::= 40
ub-physical-office-name     INTEGER ::= 128
ub-telephone-number         INTEGER ::= 32
ub-x121-address             INTEGER ::= 15
ub-isdn-address             INTEGER ::= 16
ub-destination-indicator    INTEGER ::= 128
ub-user-password            INTEGER ::= 128
-- ub-name                     INTEGER ::= 64
ub-name                     INTEGER ::= 32768
ub-ipAddress                INTEGER ::= 256


-- ObjectClass     ::= OBJECT IDENTIFIER
AliasedObjectName ::=   DistinguishedName

-- NOTE:  We invent a shorthand syntax that yields an identical
--        encoding.  GenName takes care of the CaseIgnoreSyntax
--        structure.  Those who like typing can use the 
--        commented-out version below.

GenName ::= DirectoryString

DirectoryString ::= CHOICE {
    printableString	PrintableString (SIZE(1..ub-name)),
    utf8String          UTF8String (SIZE(1..ub-name)),
    teletexString	TeletexString (SIZE(1..ub-name))
--    universalString	UniversalString (SIZE(1..ub-name)),
--    bMPString 		BMPString
      }

-- CaseIgnoreSyntax ::= CHOICE {
--    printable PrintableString,
--    teletex TeletexString}

-- GenName ::= CaseIgnoreSyntax


ID ::= OBJECT IDENTIFIER
id-attribute-types  ID ::=  {2.5.4}
id-at               ID ::=  {2.5.4}
id-objectClass             ID ::= {id-attribute-types 0}
id-aliasedObjectName       ID ::= {id-attribute-types 1}
id-knowledgeInformation    ID ::= {id-attribute-types 2}
id-commonName              ID ::= {id-attribute-types 3}
id-surname                 ID ::= {id-attribute-types 4}
id-serialNumber            ID ::= {id-attribute-types 5}
id-countryName             ID ::= {id-attribute-types 6}
id-localityName            ID ::= {id-attribute-types 7}
id-stateOrProvinceName     ID ::= {id-attribute-types 8}
id-streetAddress           ID ::= {id-attribute-types 9}
id-organizationName        ID ::= {id-attribute-types 10}
id-organizationalUnitName  ID ::= {id-attribute-types 11}
id-title                   ID ::= {id-attribute-types 12}
id-description             ID ::= {id-attribute-types 13}
id-searchGuide             ID ::= {id-attribute-types 14}
id-businessCategory        ID ::= {id-attribute-types 15}
id-postalAddress           ID ::= {id-attribute-types 16}
id-postalCode              ID ::= {id-attribute-types 17}
id-postOfficeBox           ID ::= {id-attribute-types 18}
id-physicalDeliveryOfficeName ID ::= {id-attribute-types 19}
id-telephoneNumber         ID ::= {id-attribute-types 20}
id-telexNumber             ID ::= {id-attribute-types 21}
id-teletexTerminalIdentifier  ID ::= {id-attribute-types 22}
id-facsimileTelephoneNumberr  ID ::= {id-attribute-types 23}
id-x121Address             ID ::= {id-attribute-types 24}
id-internationalISDNNumber ID ::= {id-attribute-types 25}
id-registeredAddress       ID ::= {id-attribute-types 26}
id-destinationIndicator    ID ::= {id-attribute-types 27}
id-preferredDeliveryMethod ID ::= {id-attribute-types 28}
id-presentationAddress     ID ::= {id-attribute-types 29}
id-supportedApplicationContext ID ::= {id-attribute-types 30}
id-member                  ID ::= {id-attribute-types 31}
id-owner                   ID ::= {id-attribute-types 32}
id-roleOccupant            ID ::= {id-attribute-types 33}
id-seeAlso                 ID ::= {id-attribute-types 34}
id-userPassword            ID ::= {id-attribute-types 35}
id-userCertificate         ID ::= {id-attribute-types 36}
id-cACertificate           ID ::= {id-attribute-types 37}
id-authorityRevocationList ID ::= {id-attribute-types 38}
id-certificateRevocationList  ID ::= {id-attribute-types 39}
id-crossCertificatePair       ID ::= {id-attribute-types 40}
id-name                    ID ::= {id-attribute-types 41}
id-ipAddress               ID ::= {1.3.6.1.4.1.42.2.11.2.1}
id-at-uniqueIdentifier     ID ::= {id-at 45}
id-emailAddress            ID ::= {1.2.840.113549.1.9.1}
id-at-dc                   ID ::= {0.9.2342.19200300.100.1.25}
END

-- $Id$ --
--
-- ***** BEGIN LICENSE BLOCK *****
-- 
-- BBN Rule Editor/Engine for Address and AS Number PKI
-- Version 3.0-beta
-- 
-- US government users are permitted unrestricted rights as
-- defined in the FAR.  
--
-- This software is distributed on an "AS IS" basis, WITHOUT
-- WARRANTY OF ANY KIND, either express or implied.
--
-- Copyright (C) Raytheon BBN Technologies Corp. 2007-2010.  All Rights Reserved.
--
-- Contributor(s):  Charles Gardiner
--
-- ***** END LICENSE BLOCK *****
--

DEFINITIONS ::=

PrivateKey ::= SEQUENCE
  {
  v INTEGER,
  n INTEGER,
  e INTEGER,
  d INTEGER,
  p INTEGER,
  q INTEGER,
  e1 INTEGER,
  e2 INTEGER,
  u INTEGER
  }

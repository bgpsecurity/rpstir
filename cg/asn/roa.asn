-- $Id$
-- Declaration for c->asn compatibility
--
--

DEFINITIONS IMPLICIT TAGS ::=
-- imports
IMPORTS AlgorithmIdentifier RPKIAlgorithmIdentifier CMSAlgorithmIdentifier
        FROM Algorithms IN Algorithms.asn,
        Extensions IPAddressOrRangeA FROM extensions IN extensions.asn,
	Certificate Version FROM certificate IN certificate.asn,
	Name FROM name IN name.asn, Manifest FROM Manifest IN manifest.asn;

-- ROA Specification

      ROA ::= SEQUENCE { 
        contentType ContentType TABLE ContentTable, 
        content [0] EXPLICIT ANY DEFINED BY contentType } 
    
      ContentType ::= OBJECT IDENTIFIER

      OID ::= OBJECT IDENTIFIER
      pkcs OID ::= {1.2.840.113549.1}

      pkcs-7 OID ::= {pkcs 7 }

      pkcs-9 OID ::= {pkcs 9}

      id-signedData OBJECT IDENTIFIER ::= { pkcs-7 2 }


      ContentTable ::= TABLE {
        signedData id-signedData SignedData }

      SignedData ::= SEQUENCE { 
        version CMSVersion,
        digestAlgorithms DigestAlgorithmIdentifiers, 
        encapContentInfo EncapsulatedContentInfo, 
        certificates [0] IMPLICIT CertificateSet OPTIONAL, 
        crls [1] IMPLICIT RevocationInfoChoices OPTIONAL, 
        signerInfos SignerInfos }

      CMSVersion ::= INTEGER 
        {
	v0 (0),
	v1 (1),
	v3 (3)
        } 
    
      DigestAlgorithmIdentifiers ::= SET OF CMSAlgorithmIdentifier

      CertificateSet ::= SET  OF Certificate

      CertificateChoices ::= CHOICE {
        certificate Certificate }

      RevocationInfoChoices ::= SET OF RevocationInfoChoice

      RevocationInfoChoice ::= CHOICE {
	crl CertificateList,
	other [1] IMPLICIT OtherRevocationInfoFormat }

      OtherRevocationInfoFormat ::= SEQUENCE {
	otherRevInfoFormat OBJECT IDENTIFIER,
	otherRevInfo ANY }

      CertificateList  ::=  SEQUENCE  {
        tbsCertList          TBSCertList,
        signatureAlgorithm   AlgorithmIdentifier,
        signatureValue       BIT STRING  }

      TBSCertList  ::=  SEQUENCE  {
        version                 Version OPTIONAL,
                                     -- if present, MUST be v2
        signature               AlgorithmIdentifier,
        issuer                  Name,
        thisUpdate              Time,
        nextUpdate              Time OPTIONAL,
        revokedCertificates     SEQUENCE OF SEQUENCE  {
             userCertificate         CertificateSerialNumber,
             revocationDate          Time,
             crlEntryExtensions      Extensions OPTIONAL
                                           -- if present, MUST be v2
                                  }  OPTIONAL,
        crlExtensions           [0]  EXPLICIT Extensions OPTIONAL
                                           -- if present, MUST be v2
         }
				  
--      Version  ::=  INTEGER  {  v1(0), v2(1), v3(2)  }

      CertificateSerialNumber  ::=  INTEGER

      Time ::= CHOICE {
        utcTime        UTCTime,
        generalTime    GeneralizedTime }

      SignerInfos ::= SET (SIZE (1..1)) OF SignerInfo 
    
      EncapsulatedContentInfo ::= SEQUENCE { 
        eContentType ContentType TABLE EContentTable, 
        eContent [0] EXPLICIT OCTET STRING DEFINED BY eContentType } 
    
      EContentTable ::= TABLE {
        roa      id-routeOriginAttestation RouteOriginAttestation,
        manifest id-roa-pki-manifest       Manifest, 
        trustAnchor id-ct-RPKITrustAnchor  Certificate }
    
      id-smime OBJECT IDENTIFIER ::= { iso(1) member-body(2) us(840) 
                                     rsadsi1(113549) pkcs1(1) pkcs9(9) 16 } 
    
      id-ct OBJECT IDENTIFIER ::= { id-smime 1 } 
    
      id-routeOriginAttestation OBJECT IDENTIFIER ::= { id-ct 24 } 
      id-roa-pki-manifest       OBJECT IDENTIFIER ::= { id-ct 26 } 
      id-ct-RPKITrustAnchor     OBJECT IDENTIFIER ::= { id-ct 33 }

      RouteOriginAttestation ::= SEQUENCE { 
        version [0] ROAversion DEFAULT v1, 
        asID   ASID, 
        ipAddrBlocks ROAIPAddrBlocks }

      ROAversion ::= INTEGER { v1(0) } ( v1) 
 
      ASID ::= INTEGER 
    
      ROAIPAddrBlocks ::= SEQUENCE OF ROAIPAddressFamily 
    
      ROAIPAddressFamily ::= SEQUENCE {
        addressFamily OCTET STRING (SIZE (2..3)),
        addresses SEQUENCE OF ROAIPAddress }
      -- Only two address families are allowed: IPv4 and IPv6

      ROAIPAddress ::= SEQUENCE {
        address  IPAddress,
        maxLength INTEGER OPTIONAL }
   
      IPAddress ::= BIT STRING

      SignerInfo ::= SEQUENCE { 
        version CMSVersion, -- Value check
        sid SignerIdentifier, 
        digestAlgorithm CMSAlgorithmIdentifier, 
        signedAttrs [0] IMPLICIT SignedAttributes OPTIONAL, 
        signatureAlgorithm SignatureAlgorithmIdentifier, 
        signature SignatureValue, 
        unsignedAttrs [1] IMPLICIT UnsignedAttributes OPTIONAL } 

      id-contentTypeAttr OBJECT IDENTIFIER ::= { pkcs-9 3 }
      id-messageDigestAttr OBJECT IDENTIFIER ::= { pkcs-9 4 }
      id-signingTimeAttr OBJECT IDENTIFIER ::= { pkcs-9 5 }
      id-binSigningTimeAttr OBJECT IDENTIFIER ::= { pkcs-9 16.2.46 }

      SignedAttributes ::= SET SIZE (0..MAX) OF Attribute

      UnsignedAttributes ::= SET SIZE (0..0) OF Attribute

      Attribute ::= SEQUENCE {
        attrType OBJECT IDENTIFIER TABLE AttrTable,
        attrValues AttributeValues }

      AttributeValues ::= SET OF ANY DEFINED BY attrType IN Attribute

    AttrTable ::= TABLE {
      contentType  id-contentTypeAttr OBJECT IDENTIFIER,
      messageDigest id-messageDigestAttr OCTET STRING,
      signingTime  id-signingTimeAttr SigningTime,
      binSigningTime id-binSigningTimeAttr INTEGER,
      ignored 0xFFFF ANY }

    SigningTime ::= CHOICE {
      utcTime     UTCTime,
      generalizedTime GeneralizedTime }
    

--      AttributeValue ::= ANY
 
      SignatureAlgorithmIdentifier ::= RPKIAlgorithmIdentifier

      SignerIdentifier ::= CHOICE { 
        issuerAndSerialNumber IssuerAndSerialNumber, 
        subjectKeyIdentifier [0] SubjectKeyIdentifier } 

      IssuerAndSerialNumber ::= SEQUENCE {
        issuer Name,
        serialNumber CertificateSerialNumber }

      SignatureValue ::= OCTET STRING 
    
      SubjectKeyIdentifier ::= OCTET STRING


    DigestInfo ::= SEQUENCE
      {
      digestAlgorithm OBJECT IDENTIFIER,
      digest OCTET STRING
      }

--  CMS Blob Specification (where eContent can be anything)

    CMSBlob ::= SEQUENCE {
        contentType ContentType TABLE BlobContentTable,
        content [0] EXPLICIT ANY DEFINED BY contentType }

    BlobContentTable ::= TABLE {
        signedData id-signedData BlobSignedData }

    BlobSignedData ::= SEQUENCE {
        version CMSVersion,
        digestAlgorithms DigestAlgorithmIdentifiers,
        encapContentInfo BlobEncapsulatedContentInfo,
        certificates [0] IMPLICIT CertificateSet OPTIONAL,
        crls [1] IMPLICIT RevocationInfoChoices OPTIONAL,
        signerInfos SignerInfos }

    BlobEncapsulatedContentInfo ::= SEQUENCE {
        eContentType ContentType TABLE BlobEContentTable,
        eContent [0] EXPLICIT OCTET STRING DEFINED BY eContentType }

    BlobEContentTable ::= TABLE {
        unknown 0xFFFF ANY }

-- Dec 20 2000 511E  */
-- Dec 20 2000 PFOLEY added id_sha1_with_dsa as OPTIONAL params
-- Nov 13 2000 466E  */
-- Nov 13 2000 GARDINER started
-- sfcsid = "@(#)algorithms.asn 511E"
-- File:     Algorithms.asn
-- Contents: Algorithm identifiers and definitions.
-- System:   Pkim development.
-- Created:  1-Aug-1995
-- Author:   jlowry
--
-- Remarks:  This file is separate because ASN_GEN 1.4 cannot support
--           multiple definers for ANY DEFINED BY.
--	     NOTE ALSO: The SIGNED MACRO uses the AlgorithmIdentifier and
--	     will be constrained to the TABLE specified.  
--
--	     i.e. asn_gen only supports one TABLE for SIGNED and it must govern
--	     all algorithms.  Later versions of asn_gen may fix this.
--	     See jlowry for details.
--
-- $Header: /u4/PKI/cms3_3/Libraries/Dev/rcs/lib/asndefs/Algorithms.asn,v 1.7 1997/12/05 17:32:41 mcasagni Exp $ 
--
-- COPYRIGHT 1995 BBN Systems and Technologies, A Division of BBN Inc.
-- 150 CambridgePark Drive
-- Cambridge, Ma. 02140
-- 617-873-4000

Algorithms DEFINITIONS ::=  -- explicit tags from X.509 !
BEGIN

EXPORTS
    DSAParameters, DSASignature, AlgorithmIdentifier;

AlgorithmIdentifier ::= SEQUENCE {
	algorithm OBJECT IDENTIFIER TABLE AlgorithmTable,
	parameters ANY DEFINED BY algorithm OPTIONAL }

-- NOTE:
-- There is a bug in ASNv1.5 that causes virtual destructors to be called
-- incorrectly when a table is embedded within an automatic variable.
-- Consequently, we use the OPTIONAL flag to work around.

AlgorithmTable ::= TABLE {
    sdnsSignatureAlgorithm         id-sdnsSignatureAlgorithm           NONE,
    mosaicSignatureAlgorithm       id-mosaicSignatureAlgorithm         Dss-Parms OPTIONAL,
    sdnsConfidentialityAlgorithm   id-sdnsConfidentialityAlgorithm     NONE,
    mosaicConfidentialityAlgorithm id-mosaicConfidentialityAlgorithm   Skipjack-Parm OPTIONAL,
    sdnsIntegrityAlgorithm         id-sdnsIntegrityAlgorithm           NONE,
    mosaicIntegrityAlgorithm       id-mosaicIntegrityAlgorithm         NONE,
    sdnsTokenProtectionAlgorithm   id-sdnsTokenProtectionAlgorithm     NONE,
    mosaicTokenProtectionAlgorithm id-mosaicTokenProtectionAlgorithm   NONE,
    sdnsKeyManagementAlgorithm     id-sdnsKeyManagementAlgorithm       NONE,
    mosaicKeyManagementAlgorithm   id-mosaicKeyManagementAlgorithm     Kea-Parms OPTIONAL,
    sdnsKMandSigAlgorithms         id-sdnsKMandSigAlgorithms           NONE,
    mosaicKMandSigAlgorithms       id-mosaicKMandSigAlgorithms         Kea-Dss-Parms OPTIONAL,
    secsig-MD4withRSA              id-secsig-MD4withRSA                NONE,
    secsig-MD5withRSA              id-secsig-MD5withRSA                NONE,
    secsig-MD4withRSAEncryption    id-secsig-MD4withRSAEncryption      NULL, --  Uses PKCS version of RSA.
    secsig-DES-ECB                 id-secsig-DES-ECB                   NONE,  
    secsig-DES-CBC                 id-secsig-DES-CBC                   IV OPTIONAL,
    secsig-DES-OFB                 id-secsig-DES-OFB                   FBParameter OPTIONAL,
    secsig-DES-CFB                 id-secsig-DES-CFB                   FBParameter OPTIONAL,
    secsig-DES-MAC                 id-secsig-DES-MAC                   NumberOfBits OPTIONAL,   -- the length of the MAC (constrained by comment to 16, 24, 32, 40, 48 or 64 bits).
    secsig-RSA                     id-secsig-RSA                       NONE, -- RSA Signature per ISO 9796 and ANSI X9.31
    secsig-DSA                     id-secsig-DSA                       DSAParameters OPTIONAL, 
    secsig-DSAwithSHA              id-secsig-DSAwithSHA                DSAParameters OPTIONAL,
    secsig-DSAwithSHA-1            id-secsig-DSAwithSHA-1              DSAParameters OPTIONAL,
    secsig-MDC-2withRSASignature   id-secsig-MDC-2withRSASignature     NONE,
    secsig-SHAwithRSASignature     id-secsig-SHAwithRSASignature       NONE,  
    secsig-SHA-1withRSASignature   id-secsig-SHA-1withRSASignature     NONE,  
    secsig-diffieHellman           id-secsig-diffieHellman             NONE,
    secsig-DES-EDE                 id-secsig-DES-EDE                   NONE, -- Triple DES in ECB mode, per ANSI X9.17.
    secsig-SHA                     id-secsig-SHA                       NONE,  
    secsig-MDC-2                   id-secsig-MDC-2                     NONE, --   DES-based hash algorithm to be published in ANSI X9.31 Part 2.
    secsig-DSA-Common              id-secsig-DSA-Common                NONE,  
    secsig-DSACommonWithSHA        id-secsig-DSACommonWithSHA          DSA-Common OPTIONAL,   -- (DSA with common (NULL) parameters, )
    secsig-MD2withRSASignature     id-secsig-MD2withRSASignature       NONE,  
    secsig-MD5withRSASignature     id-secsig-MD5withRSASignature       NONE,  
    rsadsi-MD2                     id-rsadsi-MD2                       NULL ,  
    rsadsi-MD4                     id-rsadsi-MD4                       NULL ,  
    rsadsi-MD5                     id-rsadsi-MD5                       NULL ,  
    rsadsi-MD2withRSAEncryption    id-rsadsi-MD2withRSAEncryption      NULL , -- Uses PKCS version of RSA.
    rsadsi-MD5withRSAEncryption    id-rsadsi-MD5withRSAEncryption      NULL , -- Uses PKCS version of RSA.
    rsadsi-rsaEncryption           id-rsadsi-rsaEncryption             NULL , -- used for encryption and signature
    rsadsi-diffieHellman           id-rsadsi-diffieHellman             DiffieHellmanParameters OPTIONAL,
    rsadsi-RC2-CBC                 id-rsadsi-RC2-CBC                   NONE, --  Proprietary symmetric block encryption algorithm from RSADSI
    rsadsi-RC4                     id-rsadsi-RC4                       NONE, --  Proprietary stream cipher algorithm from RSADSI
    dssig-ElGamal                  id-dssig-ElGamal                    NONE,   
    dssig-MD2withRSA               id-dssig-MD2withRSA                 NONE, -- This uses the X.509 version of RSA.
    dssig-MD2withElGamal           id-dssig-MD2withElGamal             NONE,   
    dsa                            id-dsa                              DSAParameters OPTIONAL,
    dsa-with-sha1                  id-dsa-with-sha1                    NULL OPTIONAL,
    rsadsi-SHA-1WithRSAEncryption  id-sha-1WithRSAEncryption           NULL,
    unknown                         0xFFFF                             ANY OPTIONAL
}

Dss-Parms ::= SEQUENCE {
    p	OCTET STRING , 
    q	OCTET STRING , 
    g	OCTET STRING }

Kea-Parms ::= SEQUENCE {
    p   OCTET STRING , 
    q   OCTET STRING , 
    g   OCTET STRING }

Kea-Dss-Parms ::= CHOICE {
    diffParms	[0] Different-Parms,
    commonParms [1] Common-Parms }

Different-Parms ::= SEQUENCE {
    keaparms    Kea-Parms,
    dssparms	Dss-Parms }

Common-Parms ::= SEQUENCE {
    p	OCTET STRING , 
    q	OCTET STRING , 
    g	OCTET STRING }

Skipjack-Parm ::= SEQUENCE {
    initvector OCTET STRING }

-- Object Identifiers

ID ::= OBJECT IDENTIFIER

-- joint-iso-ccitt     ID ::= 2
-- country             ID ::= 16
-- us                  ID ::= 840
-- organization        ID ::= 1
-- us-government       ID ::= 101
-- dod                 ID ::= 2

id-infosec  ID ::=  {2.16.840.1.101.2.1}

id-modules                          ID ::= {id-infosec 0}
id-algorithms                       ID ::= {id-infosec 1}
id-formats                          ID ::= {id-infosec 2}
id-policy                           ID ::= {id-infosec 3}
id-object-classes                   ID ::= {id-infosec 4}
id-attributes                       ID ::= {id-infosec 5}
				        
id-sdnsSignatureAlgorithm           ID  ::= {id-algorithms 1}
id-mosaicSignatureAlgorithm         ID  ::= {id-algorithms 2}
id-sdnsConfidentialityAlgorithm     ID  ::= {id-algorithms 3}
id-mosaicConfidentialityAlgorithm   ID  ::= {id-algorithms 4}
id-sdnsIntegrityAlgorithm           ID  ::= {id-algorithms 5}
id-mosaicIntegrityAlgorithm         ID  ::= {id-algorithms 6}
id-sdnsTokenProtectionAlgorithm     ID  ::= {id-algorithms 7}
id-mosaicTokenProtectionAlgorithm   ID  ::= {id-algorithms 8}
id-sdnsKeyManagementAlgorithm       ID  ::= {id-algorithms 9}
id-mosaicKeyManagementAlgorithm     ID  ::= {id-algorithms 10}
id-sdnsKMandSigAlgorithms           ID  ::= {id-algorithms 11}
id-mosaicKMandSigAlgorithms         ID  ::= {id-algorithms 12}
id-keyEncryptionAlgorithm           ID  ::= {id-algorithms 22}
				        
id-msp-content-type                 ID  ::= {id-formats 48}
id-msp-rev3-content-type            ID  ::= {id-formats 42}
id-msp-rekey-agent-protocol         ID  ::= {id-formats 49}
id-rfc822-message-format            ID  ::= {id-formats 1}
id-empty-content                    ID  ::= {id-formats 2}
forwarded-MSP-message-body-part     ID  ::= {id-formats 72}
				        
id-sdns-security-policy-id          ID  ::= {id-policy 1}
id-sdns-prbac-id                    ID  ::= {id-policy 2}
id-mosaic-prbac-id                  ID  ::= {id-policy 3}
				    
id-msp-user-sdns                    ID  ::= {id-object-classes 1}
id-mail-list                        ID  ::= {id-object-classes 2}
id-dsa-sdns                         ID  ::= {id-object-classes 3}
id-ca-sdns                          ID  ::= {id-object-classes 4}
id-crls-sdns                        ID  ::= {id-object-classes 5}
id-msp-user-mosaic                  ID  ::= {id-object-classes 6}
id-dsa-mosaic                       ID  ::= {id-object-classes 7}
id-ca-mosaic                        ID  ::= {id-object-classes 8}

id-sdnsKeyManagementCertificate     ID  ::= {id-attributes 1}
id-sdnsUserSignatureCertificate     ID  ::= {id-attributes 2}
id-sdnsKMandSigCertificate          ID  ::= {id-attributes 3}
id-mosaicKeyManagementCertificate   ID  ::= {id-attributes 4}
id-mosaicKMandSigCertificate        ID  ::= {id-attributes 5}
id-mosaicUserSignatureCertificate   ID  ::= {id-attributes 6}
id-mosaicCASignatureCertificate     ID  ::= {id-attributes 7}
id-sdnsCASignatureCertificate       ID  ::= {id-attributes 8}
id-auxiliaryVector                  ID  ::= {id-attributes 10}
id-mlReceiptPolicy                  ID  ::= {id-attributes 11}
id-mlMembership                     ID  ::= {id-attributes 12}
id-mlAdministrators                 ID  ::= {id-attributes 13}
id-mlid                             ID  ::= {id-attributes 14}
id-janUKMs                          ID  ::= {id-attributes 20}
id-febUKMs                          ID  ::= {id-attributes 21}
id-marUKMs                          ID  ::= {id-attributes 22}
id-aprUKMs                          ID  ::= {id-attributes 23}
id-mayUKMs                          ID  ::= {id-attributes 24}
id-junUKMs                          ID  ::= {id-attributes 25}
id-julUKMs                          ID  ::= {id-attributes 26}
id-augUKMs                          ID  ::= {id-attributes 27}
id-sepUKMs                          ID  ::= {id-attributes 28}
id-octUKMs                          ID  ::= {id-attributes 29}
id-novUKMs                          ID  ::= {id-attributes 30}
id-decUKMs                          ID  ::= {id-attributes 31}
id-metaSDNScrl                      ID  ::= {id-attributes 40}
id-sdnsCRL                          ID  ::= {id-attributes 41}
id-metaSDNSsignatureCRL             ID  ::= {id-attributes 42}
id-SDNSsignatureCRL                 ID  ::= {id-attributes 43}
id-sdnsCertificateRevocationList    ID  ::= {id-attributes 44}
id-mosaicCertificateRevocationList  ID  ::= {id-attributes 45}
id-mosaicKRL                        ID  ::= {id-attributes 46}
id-mlExemptedAddressProcessor       ID  ::= {id-attributes 47}

-- The Security Special Interest Group (secsig).
-- Many of these are official NIST OIDs.
-- { iso(1) identified-organization(3) oiw(14) secsig(3) algorithm(2) }
secsig-algorithm                ID ::= {1.3.14.3.2} 
id-secsig-MD4withRSA            ID ::= { secsig-algorithm 2 }
id-secsig-MD5withRSA            ID ::= { secsig-algorithm 3 }
id-secsig-MD4withRSAEncryption  ID ::= { secsig-algorithm 4 }  
id-secsig-DES-ECB               ID ::= { secsig-algorithm 6 }
id-secsig-DES-CBC               ID ::= { secsig-algorithm 7 }  
id-secsig-DES-OFB               ID ::= { secsig-algorithm 8 }  
id-secsig-DES-CFB               ID ::= { secsig-algorithm 9 }  
id-secsig-DES-MAC               ID ::= { secsig-algorithm 10 } 
id-secsig-RSA                   ID ::= { secsig-algorithm 11 } 
id-secsig-DSA                   ID ::= { secsig-algorithm 12 } 
id-secsig-DSAwithSHA            ID ::= { secsig-algorithm 13 } 
id-secsig-MDC-2withRSASignature ID ::= { secsig-algorithm 14 }
id-secsig-SHAwithRSASignature   ID ::= { secsig-algorithm 15 }
id-secsig-diffieHellman         ID ::= { secsig-algorithm 16 } 
id-secsig-DES-EDE               ID ::= { secsig-algorithm 17 } 
id-secsig-SHA                   ID ::= { secsig-algorithm 18 }
id-secsig-MDC-2                 ID ::= { secsig-algorithm 19 } 
id-secsig-DSA-Common            ID ::= { secsig-algorithm 20 }
id-secsig-DSACommonWithSHA      ID ::= { secsig-algorithm 21 } 
id-secsig-MD2withRSASignature   ID ::= { secsig-algorithm 22 }
id-secsig-MD5withRSASignature   ID ::= { secsig-algorithm 23 }
id-secsig-DSAwithSHA-1          ID ::= { secsig-algorithm 27 } 
id-secsig-SHA-1withRSASignature ID ::= { secsig-algorithm 29 }

-- RSA Data Security IDs
-- { iso(1) member-body(2) US(840) rsadsi(113549) }
rsadsi                          ID ::= {1.2.840.113549}  
rsadsi-digestAlgorithm          ID ::= {rsadsi 2}
rsadsi-encryptionAlgorithm      ID ::= {rsadsi 3}
pkcs                            ID ::= {rsadsi 1}
pkcs-1                          ID ::= {pkcs 1}
pkcs-3                          ID ::= {pkcs 3}
id-rsadsi-MD2                   ID ::= { rsadsi-digestAlgorithm 2 }
id-rsadsi-MD4                   ID ::= { rsadsi-digestAlgorithm 4 }
id-rsadsi-MD5                   ID ::= { rsadsi-digestAlgorithm 5 }
id-rsadsi-MD2withRSAEncryption  ID ::= { pkcs-1 2 } -- Uses PKCS version of RSA.
id-rsadsi-MD5withRSAEncryption  ID ::= { pkcs-1 4 } -- Uses PKCS version of RSA.
id-rsadsi-rsaEncryption         ID ::= { pkcs-1 1 } -- used for encryption and signature
id-rsadsi-diffieHellman         ID ::= { pkcs-3 1 } -- DiffieHellmanParameters
id-rsadsi-RC2-CBC               ID ::= { rsadsi-encryptionAlgorithm 2 } --  Proprietary symmetric block encryption algorithm from RSADSI
id-rsadsi-RC4                   ID ::= { rsadsi-encryptionAlgorithm 4 } --  Proprietary stream cipher algorithm from RSADSI
id-sha-1WithRSAEncryption       ID ::= { pkcs-1 5 }
-- Directory Services Special Interest Group, e.g. X.500/ISO 9796 
-- { iso(1) identified-organization(3) oiw(14) dssig(7) algorithm(2) }
dssig-algorithm                 ID ::= {1.3.14.7.2}  
dssig-encryption-algorithm      ID ::= {dssig-algorithm 1}
dssig-signature-algorithm       ID ::= {dssig-algorithm 3}
id-dssig-ElGamal                ID ::= { dssig-encryption-algorithm 1 }
id-dssig-MD2withRSA             ID ::= { dssig-signature-algorithm 1 } -- This uses the X.509 version of RSA.
id-dssig-MD2withElGamal         ID ::= { dssig-signature-algorithm 2 }

-- X9 Algorithm
-- { iso(1) member-body(2) us(840) x9-57(10040) x9algorithm(4) }
id-x9                           ID ::=  {1.2.840.10040.4}
id-dsa                          ID ::= {id-x9 1}
id-dsa-with-sha1                ID ::= {id-x9 3} 

-- DN public number
-- { iso(1) member-body(2) us(840) ansi-x942(10046) 1 }
dnpublicnumber OBJECT IDENTIFIER  ::= { iso(1) member-body(2)
               us(840) ansi-x942(10046) 1 }

KEA-Parms-Id ::= OCTET STRING

DiffieHellmanParameters ::=  SEQUENCE {   -- pkcs-3(3)
    prime  INTEGER,     -- p
    base  INTEGER,      -- g
    privateValueLength INTEGER OPTIONAL }

DSAParameters ::= SEQUENCE {        -- secsig-algorithm 19
    prime1            INTEGER,      -- modulus p
    prime2            INTEGER,      -- modulus q
    base              INTEGER }     -- base g

DSASignature ::= SEQUENCE {
    arr               INTEGER,      -- first half of DSA signature
    ess               INTEGER }     -- second half of DSA signature

DSA-Common ::= NULL

FBParameter ::= SEQUENCE {
    iv                IV,
    numberOfBits      NumberOfBits }

IV ::= OCTET STRING
NumberOfBits ::= INTEGER     -- number of feedback bits (1-64)


END
